FME workspace OS Open Rivers Loader.fmw
Title: Ordnance Survey Open Rivers - Loader
Description: Ordnance Survey Open Rivers - Loader
This workbook takes the Ordnance Survey Open Rivers Data and saves it as both FileGDB on a local machine and also as ArcSDE in the OSDATA database.
There is no actual conversion of the data,the duplicate filter does what it says, but as this is a National dataset none should be found as data does not cross grid squares.  The geometry filter just splits the data by WatercourseLink or HydroNode.
History: 13/09/2017,A. Ingall,Initial Build

Parameters:
- DestDataset_GEODATABASE_FILE = D:\Ordnance Survey\OS_OpenMap_Rivers\OpenMapRivers.gdb   # File Geodatabase
- SourceDataset_ESRISHAPE = ""H:\Downloads\oprvrs_essh_gb\data\HydroNode.shp" "H:\Downloads\oprvrs_essh_gb\data\WatercourseLink.shp""   # Source Esri Shapefile(s)
- FEATURE_TYPES =

Readers:
- ESRISHAPE_1: ESRISHAPE from $(SourceDataset_ESRISHAPE)

Writers:
- GEODATABASE_FILE_1: GEODATABASE_FILE to $(DestDataset_GEODATABASE_FILE) in OSGB-GPS-2015
- GEODATABASE_SDE_1: GEODATABASE_SDE

Note: Version History / Date / Version / Change By / Changes / 13/09/2017 / 1 / A. Ingall / Initial Build
Note: Contact Details / Andrew Ingall / Basingstoke and Deane Borough Council / andrew.ingall@basingstoke.gov.uk
Note: Ordnance Survey Open Rivers - Loader
Note: Workbook Description / This workbook takes the Ordnance Survey Open Rivers Data and saves it as both FileGDB on a local machine and also as ArcSDE in the OSDATA database. / There is no actual conversion of the data,the duplicate filter does what it says, but as this is a National dataset none should be found as data does not cross grid squares. The geometry filter just splits the data by WatercourseLink or HydroNode.

Bookmark: Data Reader
HydroNode (reader ESRISHAPE_1)
    attributes: identifier char(38), formOfNode char(65), name1 char(250), form char(50), length short, endNode char(38), fictitious char(5), flow char(60), name2 char(250), startNode char(38)
    -> DuplicateFilter

Bookmark: Duplicate Filter
DuplicateFilter
    KEYATTR = identifier
    INPUT_ORDERED_CHOICE = No
    UNIQUE -> GeometryFilter

Bookmark: Geometry Filter
GeometryFilter
    INSTANTIATE = No
    GEOM_PORT_NAMES = Point Line
    BREAK_AGG = Yes
    POINT -> RoadLink00 (writer GEODATABASE_FILE_1)
    POINT -> Junction
    LINE -> Junction_3
    LINE -> RoadLink (writer GEODATABASE_FILE_1)

Bookmark: Ordnance Survey Open Roads
Junction
    -> Junction_2
Junction_3
    -> Junction_4

Bookmark: Data Writer
Junction_2
    -> TV_RoadNode (writer GEODATABASE_SDE_1)
Junction_4
    -> WatercourceLink (writer GEODATABASE_SDE_1)

Bookmark: Node Writer
TV_RoadNode (writer GEODATABASE_SDE_1)
    attributes: identifier char(38), formOfNode char(20), name1 char(150), form char(50), length integer, endNode char(38), fictitious char(5), flow char(60), name2 char(150), startNode char(38)

Bookmark: Node Writer
RoadLink00 (writer GEODATABASE_FILE_1)
    attributes: identifier char(38), formOfNode char(20), name1 char(150), form char(50), length integer, endNode char(38), fictitious char(5), flow char(60), name2 char(150), startNode char(38)

Bookmark: River Link Writer
WatercourceLink (writer GEODATABASE_SDE_1)
    attributes: identifier char(38), formOfNode char(20), name1 char(150), form char(50), length integer, endNode char(38), fictitious char(5), flow char(60), name2 char(150), startNode char(38)

Bookmark: River Link Writer
RoadLink (writer GEODATABASE_FILE_1)
    attributes: identifier char(38), formOfNode char(20), name1 char(150), form char(50), length integer, endNode char(38), fictitious char(5), flow char(60), name2 char(150), startNode char(38)
