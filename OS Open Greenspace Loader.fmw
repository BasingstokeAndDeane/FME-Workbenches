FME workspace OS Open Greenspace Loader.fmw
Title: Ordnance Survey Open Rivers - Loader
Description: Ordnance Survey Open Rivers - Loader
This workbook takes the Ordnance Survey Open Rivers Data and saves it as both FileGDB on a local machine and also as ArcSDE in the OSDATA database.
There is no actual conversion of the data,the duplicate filter does what it says, but as this is a National dataset none should be found as data does not cross grid squares.  The geometry filter just splits the data by WatercourseLink or HydroNode.
History: 13/09/2017,A. Ingall,Initial Build

Parameters:
- DestDataset_GEODATABASE_FILE = D:\Ordnance Survey\OS_Mastermap_GreenSpace\GreenspaceOpen.gdb   # File Geodatabase
- SourceDataset_ESRISHAPE = ""H:\Downloads\opgrsp_essh_gb\OS Open Greenspace (ESRI Shape File) GB\data\GB_AccessPoint.shp" "H:\Downloads\opgrsp_essh_gb\OS Open Greenspace (ESRI Shape File) GB\data\GB_GreenspaceSite.shp""   # Source Esri Shapefile(s)
- FEATURE_TYPES =

Readers:
- ESRISHAPE_1: ESRISHAPE from $(SourceDataset_ESRISHAPE)

Writers:
- GEODATABASE_FILE_1: GEODATABASE_FILE to $(DestDataset_GEODATABASE_FILE) in OSGB-GPS-2015
- GEODATABASE_SDE_1: GEODATABASE_SDE

Note: Version History / Date / Version / Change By / Changes / 13/09/2017 / 1 / A. Ingall / Initial Build
Note: Ordnance Survey Open Greenspace - Loader
Note: Workbook Description / This workbook takes the Ordnance Survey Open Greenspace Data and saves it as both FileGDB on a local machine and also as ArcSDE in the OSDATA database. / There is no actual conversion of the data,the duplicate filter does what it says, but as this is a National dataset none should be found as data does not cross grid squares. The geometry filter just splits the data by WatercourseLink or HydroNode.

Bookmark: Data Reader
GB_AccessPoint (reader ESRISHAPE_1)
    attributes: id char(38), accessType char(40), refToGSite char(38), distName3 char(254), distName2 char(254), distName1 char(254), function char(40), distName4 char(254)
    -> StringReplacer_2

Bookmark: String Replacer
StringReplacer_2
    CASE = NO
    SRC_ATTRS = fme_feature_type
    FIND_TEXT = ^.{3}(.+)$
    REGEXP = YES
    REPLACE_TEXT = \1
    NO_MATCH = _FME_NO_OP_
    -> DuplicateFilter

Bookmark: Duplicate Filter
DuplicateFilter
    INPUT_ORDERED_CHOICE = No
    KEYATTR = id
    UNIQUE -> GeometryValidator

Bookmark: Ordnance Survey Open Greenspace Loader
GeometryValidator
    TYPE_REPAIR = TYPE_REPAIR
    SELF_INTERSECTING = SELF_INTERSECTING
    PLANAR_SURFACE = PLANAR_SURFACE
    PRESETS = All
    CONSECUTIVE_IDENTICAL_VERTICES_2D = CONSECUTIVE_IDENTICAL_VERTICES_2D
    CHECK_HOLE_TOUCHING_POLYGON = No
    THICKNESS_TOLERANCE_CHOICE = Automatic
    ORIENTATION_CHECK_DIR = Valid
    REPAIR = Yes
    ARC_ENDPOINT_TOLERANCE_MODE = Auto
    AREA_ORIENTATION = AREA_ORIENTATION
    NAN_REMOVAL = NAN_REMOVAL
    MISSING_TEXTURE_COORDINATES = MISSING_TEXTURE_COORDINATES
    OGC_VALID_CHECK = OGC_VALID_CHECK
    OGC_VERSION_CHOICE = 1.2.0
    FLIP_APPEARANCES_CHOICE = Yes
    ANGULAR_TOLERANCE_CHOICE = Automatic
    MISSING_VERTEX_NORMALS = MISSING_VERTEX_NORMALS
    CONNECT_Z_MODE_SI = First Wins
    SUMMARY = Detailed
    CONNECT_Z_MODE_TR = First Wins
    DUP_COORDS_CHECK_Z = Yes
    NULL_REMOVAL = NULL_REMOVAL
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    OGC_SIMPLE_CHECK = OGC_SIMPLE_CHECK
    SHELL_VALIDATION = SHELL_VALIDATION
    CHECK_AREA_CHOICE = No
    ISSUE_ATTR_NAME = _issues
    SOLID_VOID_REPAIR = SOLID_VOID_REPAIR
    PASSED -> GeometryFilter
    REPAIRED -> GeometryFilter
Junction
    -> Junction_2
Junction_3
    -> Junction_4

Bookmark: Geometry Filter
GeometryFilter
    INSTANTIATE = No
    GEOM_PORT_NAMES = Point Area
    BREAK_AGG = Yes
    POINT -> RoadLink00 (writer GEODATABASE_FILE_1)
    POINT -> Junction
    AREA -> RoadLink (writer GEODATABASE_FILE_1)
    AREA -> Junction_3

Bookmark: Data Writer
Junction_2
    -> TV_RoadNode (writer GEODATABASE_SDE_1)
Junction_4
    -> WatercourceLink (writer GEODATABASE_SDE_1)

Bookmark: AccessPoint Writer
TV_RoadNode (writer GEODATABASE_SDE_1)
    attributes: id char(38), accessType char(40), refToGSite char(38), distName3 char(254), distName2 char(254), distName1 char(254), function char(40), distName4 char(254)

Bookmark: AccessPoint Writer
RoadLink00 (writer GEODATABASE_FILE_1)
    attributes: id char(38), accessType char(40), refToGSite char(38), distName3 char(254), distName2 char(254), distName1 char(254), function char(40), distName4 char(254)

Bookmark: Greenspace Area Writer
WatercourceLink (writer GEODATABASE_SDE_1)
    attributes: id char(38), accessType char(40), refToGSite char(38), distName3 char(254), distName2 char(254), distName1 char(254), function char(40), distName4 char(254)

Bookmark: Greenspace Area Writer
RoadLink (writer GEODATABASE_FILE_1)
    attributes: id char(38), accessType char(40), refToGSite char(38), distName3 char(254), distName2 char(254), distName1 char(254), function char(40), distName4 char(254)
